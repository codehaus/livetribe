AGENTPP-GLOBAL-REG DEFINITIONS ::= BEGIN

IMPORTS
	enterprises,
	MODULE-IDENTITY,
	OBJECT-IDENTITY
		FROM SNMPv2-SMI;

agentppRegMIB MODULE-IDENTITY
	LAST-UPDATED "200405151012Z"	-- May 15, 2004 10:12:00 AM
	ORGANIZATION "AGENT++"
	CONTACT-INFO
		"Intenet: http://www.agentpp.com
		 Email:   fock@agentpp.com"
	DESCRIPTION
		"Global registration MIB module for the AGENT++
		framework."
	REVISION "200405151012Z"	-- May 15, 2004 10:12:00 AM
	DESCRIPTION
		"Updated contact information."
	REVISION "9911090000Z"	-- Nov 9, 1999 12:00:00 AM
	DESCRIPTION
		"The initial version."
	REVISION "9912010000Z"	-- Dec 1, 1999 12:00:00 AM
	DESCRIPTION
		"Removed the duplicate OBJECT-IDENTITY definition 'agentpp'
		at the end of the initial version."
 -- 1.3.6.1.4.1.4976.1.1.1 --  ::= { enterprises 4976 1 1 1 }


agentpp OBJECT-IDENTITY
	STATUS current
	DESCRIPTION
		"The root of the sub-tree assigned to AGENT++."
 -- 1.3.6.1.4.1.4976 --  ::= { enterprises 4976 }

agentppReg OBJECT-IDENTITY
	STATUS current
	DESCRIPTION
		"Sub-tree for registrations."
 -- 1.3.6.1.4.1.4976.1 --  ::= { agentpp 1 }

agentppModules OBJECT-IDENTITY
	STATUS current
	DESCRIPTION
		"Sub-tree to register the values assigned to modules
		with the MODULE-IDENTITY construct."
 -- 1.3.6.1.4.1.4976.1.1 --  ::= { agentppReg 1 }

agentppGeneric OBJECT-IDENTITY
	STATUS current
	DESCRIPTION
		"Sub-tree for common object and event definitions."
 -- 1.3.6.1.4.1.4976.2 --  ::= { agentpp 2 }

agentppProducts OBJECT-IDENTITY
	STATUS current
	DESCRIPTION
		"Sub-tree for specific object and event definitions."
 -- 1.3.6.1.4.1.4976.3 --  ::= { agentpp 3 }

agentppCaps OBJECT-IDENTITY
	STATUS current
	DESCRIPTION
		"Sub-tree for agent profiles."
 -- 1.3.6.1.4.1.4976.4 --  ::= { agentpp 4 }

agentppReqs OBJECT-IDENTITY
	STATUS current
	DESCRIPTION
		"Sub-tree for management application requirements."
 -- 1.3.6.1.4.1.4976.5 --  ::= { agentpp 5 }

agentppExpr OBJECT-IDENTITY
	STATUS current
	DESCRIPTION
		"Sub-tree for experimental definitions."
 -- 1.3.6.1.4.1.4976.6 --  ::= { agentpp 6 }

END
