AGENTPP-CONFIG-MIB DEFINITIONS ::= BEGIN

IMPORTS
	TEXTUAL-CONVENTION
		FROM SNMPv2-TC
	OBJECT-GROUP
		FROM SNMPv2-CONF
	agentppProducts
		FROM AGENTPP-GLOBAL-REG
	MODULE-IDENTITY,
	OBJECT-TYPE,
	Integer32
		FROM SNMPv2-SMI;

agentppCfgMIB MODULE-IDENTITY
	LAST-UPDATED "200311302145Z"	-- Nov 30, 2003 9:45:00 PM
	ORGANIZATION "AGENT++"
	CONTACT-INFO
		"Frank Fock
		Email: fock@agentpp.com"
	DESCRIPTION
		"This module defines MIB objects for configuration
		of AGENT++ agent features that cannot be configured
		through standard MIB modules."
	REVISION "200311302145Z"	-- Nov 30, 2003 9:45:00 PM
	DESCRIPTION
		"Initial version."
 -- 1.3.6.1.4.1.4976.3.3 --  ::= { agentppProducts 3 }


AgentppLogLevel ::= TEXTUAL-CONVENTION
	STATUS current
	DESCRIPTION
		"The AGENT++ log level is specified by an integer
		value between 0 and 15, where 0 denotes the
		highest priority. By setting the log level to zero
		only those log message with level 0 will be logged.

		If the level is set to 10, all messages with level 0
		up to 10 (inclusive) will be logged."
	SYNTAX Integer32 (0..15)


-- Scalars and Tables
--

agentppCfgObjects OBJECT IDENTIFIER 
 -- 1.3.6.1.4.1.4976.3.3.1 --  ::= { agentppCfgMIB 1 }

agentppCfgLogging OBJECT IDENTIFIER 
 -- 1.3.6.1.4.1.4976.3.3.1.1 --  ::= { agentppCfgObjects 1 }

agentppCfgLogLevelError OBJECT-TYPE
	SYNTAX AgentppLogLevel
	MAX-ACCESS read-write
	STATUS current
	DESCRIPTION
		"The the log level for log messages of the type
		ERROR."
 -- 1.3.6.1.4.1.4976.3.3.1.1.1 --  ::= { agentppCfgLogging 1 }


agentppCfgLogLevelWarning OBJECT-TYPE
	SYNTAX AgentppLogLevel
	MAX-ACCESS read-write
	STATUS current
	DESCRIPTION
		"The the log level for log messages of the type
		WARNING."
 -- 1.3.6.1.4.1.4976.3.3.1.1.2 --  ::= { agentppCfgLogging 2 }


agentppCfgLogLevelEvent OBJECT-TYPE
	SYNTAX AgentppLogLevel
	MAX-ACCESS read-write
	STATUS current
	DESCRIPTION
		"The the log level for log messages of the type
		EVENT."
 -- 1.3.6.1.4.1.4976.3.3.1.1.3 --  ::= { agentppCfgLogging 3 }


agentppCfgLogLevelInfo OBJECT-TYPE
	SYNTAX AgentppLogLevel
	MAX-ACCESS read-write
	STATUS current
	DESCRIPTION
		"The the log level for log messages of the type
		INFO."
 -- 1.3.6.1.4.1.4976.3.3.1.1.4 --  ::= { agentppCfgLogging 4 }


agentppCfgLogLevelDebug OBJECT-TYPE
	SYNTAX AgentppLogLevel
	MAX-ACCESS read-write
	STATUS current
	DESCRIPTION
		"The the log level for log messages of the type
		DEBUG."
 -- 1.3.6.1.4.1.4976.3.3.1.1.5 --  ::= { agentppCfgLogging 5 }


agentppCfgSecurity OBJECT IDENTIFIER 
 -- 1.3.6.1.4.1.4976.3.3.1.2 --  ::= { agentppCfgObjects 2 }

agentppCfgSecSrcAddrValidation OBJECT-TYPE
	SYNTAX INTEGER {
			enabled(1),
			disabled(2),
			notAvailable(3) }
	MAX-ACCESS read-write
	STATUS current
	DESCRIPTION
		"Specifies whether SNMPv1/v2c source address
		validation via the snmpTargetAddrExtTable and
		the snmpCommunityTable is enabled or disabled.

		If the value of this object is notAvailable(3), then at
		least one of the necessary MIB modules are not
		implemented for this agent instance and an attempt
		to set this object's value to enabled(1) or disabled(2)
		will result in a wrongValue error."
 -- 1.3.6.1.4.1.4976.3.3.1.2.1 --  ::= { agentppCfgSecurity 1 }


-- Notification Types
--

agentppCfgEvents OBJECT IDENTIFIER 
 -- 1.3.6.1.4.1.4976.3.3.2 --  ::= { agentppCfgMIB 2 }

-- Conformance
--

agentppCfgConf OBJECT IDENTIFIER 
 -- 1.3.6.1.4.1.4976.3.3.3 --  ::= { agentppCfgMIB 3 }

-- Groups
--

agentppCfgGroups OBJECT IDENTIFIER 
 -- 1.3.6.1.4.1.4976.3.3.3.1 --  ::= { agentppCfgConf 1 }

-- Compliance
--

agentppCfgCompls OBJECT IDENTIFIER 
 -- 1.3.6.1.4.1.4976.3.3.3.2 --  ::= { agentppCfgConf 2 }

agentppCfgBasicGroupLogging OBJECT-GROUP
	OBJECTS {
		agentppCfgLogLevelError,
		agentppCfgLogLevelWarning,
		agentppCfgLogLevelEvent,
		agentppCfgLogLevelInfo,
		agentppCfgLogLevelDebug,
		agentppCfgSecSrcAddrValidation }
	STATUS current
	DESCRIPTION
		"Basic objects for log configuration."
 -- 1.3.6.1.4.1.4976.3.3.3.1.1 --  ::= { agentppCfgGroups 1 }

agentppCfgBasicGroupSecurity OBJECT-GROUP
	OBJECTS {
		agentppCfgSecSrcAddrValidation }
	STATUS current
	DESCRIPTION
		"This group specifies basic objects for security
		configuration."
 -- 1.3.6.1.4.1.4976.3.3.3.1.2 --  ::= { agentppCfgGroups 2 }

END
