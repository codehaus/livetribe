AGENTPP-MIBEXPLORER-MIB DEFINITIONS ::= BEGIN

IMPORTS
	DisplayString,
	TAddress,
	TDomain
FROM SNMPv2-TC
	OBJECT-GROUP,
	NOTIFICATION-GROUP
FROM SNMPv2-CONF
	agentppProducts
FROM AGENTPP-GLOBAL-REG
	MODULE-IDENTITY,
	OBJECT-IDENTITY,
	OBJECT-TYPE,
	NOTIFICATION-TYPE
FROM SNMPv2-SMI;

agentppMIBExplorerMIB MODULE-IDENTITY
	LAST-UPDATED "200209230000Z"
	ORGANIZATION "AGENT++"
	CONTACT-INFO
		"Frank Fock
		mailto:fock@agentpp.com
		http://www.mibexplorer.com"
	DESCRIPTION
		"This module defines objects for the MIB Explorer
		product."
	REVISION "200209230000Z"
	DESCRIPTION
		"Initial version defines traps for sending 
		alarms with severities of INFO, WARN, 
		ERROR, and FATAL."
	::= { agentppProducts 2 }


agentppExplObjects OBJECT IDENTIFIER 	::= { agentppMIBExplorerMIB 1 }

agentppExplAlarmObjects OBJECT IDENTIFIER 	::= { agentppExplObjects 1 }

agentppExplAlarmText OBJECT-TYPE
	SYNTAX DisplayString
	MAX-ACCESS accessible-for-notify
	STATUS current
	DESCRIPTION
		"Holds the alarm text value of the alarm."
	::= { agentppExplAlarmObjects 1 }


agentppExplAlarmType OBJECT-TYPE
	SYNTAX INTEGER {
			transient(1),
			raised(2),
			cleared(3) }
	MAX-ACCESS accessible-for-notify
	STATUS current
	DESCRIPTION
		"Specifies whether the alarm is transient or 
		whether it is raised or cleared."
	::= { agentppExplAlarmObjects 2 }


agentppExplAlarmGenerator OBJECT-TYPE
	SYNTAX DisplayString
	MAX-ACCESS accessible-for-notify
	STATUS current
	DESCRIPTION
		"The name of the sub system that generated the
		alarm."
	::= { agentppExplAlarmObjects 3 }


agentppExplAlarmSourceDescr OBJECT-TYPE
	SYNTAX DisplayString
	MAX-ACCESS accessible-for-notify
	STATUS current
	DESCRIPTION
		"A textual description of the system that caused
		this alarm."
	::= { agentppExplAlarmObjects 4 }


agentppExplAlarmSourceAddress OBJECT-TYPE
	SYNTAX TAddress
	MAX-ACCESS accessible-for-notify
	STATUS current
	DESCRIPTION
		"The address of the system that caused this alarm."
	::= { agentppExplAlarmObjects 5 }


agentppExplAlarmSourceDomain OBJECT-TYPE
	SYNTAX TDomain
	MAX-ACCESS accessible-for-notify
	STATUS current
	DESCRIPTION
		"The domain of the source address of the system
		that caused this alarm."
	::= { agentppExplAlarmObjects 6 }


agentppExplNotifications OBJECT IDENTIFIER 	::= { agentppMIBExplorerMIB 2 }

agentppExplTraps OBJECT IDENTIFIER 	::= { agentppExplNotifications 0 }

agentppExplConformance OBJECT IDENTIFIER 	::= { agentppMIBExplorerMIB 3 }

agentppExplObjectGroups OBJECT IDENTIFIER 	::= { agentppExplConformance 1 }

agentppExplNotificationGroups OBJECT IDENTIFIER 	::= { agentppExplConformance 2 }


agentppExplAlarmINFO NOTIFICATION-TYPE
	OBJECTS {
		agentppExplAlarmText,
		agentppExplAlarmType,
		agentppExplAlarmGenerator,
		agentppExplAlarmSourceDescr}
	STATUS current
	DESCRIPTION
		"This notification defines an alarm with INFO severity.
		The INFO severity designates informational messages
		that highlight the progress of a process at coarse-grained
		level.

		The payload includes information generated by a MIB 
		Explorer monitor alarm. 

		The objects agentppExplAlarmSourceAddress and
		agentppExplAlarmSourceDomain are not included in
		this definition but may be optionally appended if the
		corresponding information is available when this
		notification is being generated."
	::= { agentppExplTraps 1 }


agentppExplAlarmWARN NOTIFICATION-TYPE
	OBJECTS {
		agentppExplAlarmText,
		agentppExplAlarmType,
		agentppExplAlarmGenerator,
		agentppExplAlarmSourceDescr}
	STATUS current
	DESCRIPTION
		"This notification defines an alarm with WARN severity.
		The WARN severity designates potentially harmful
		situations.

		The payload includes information generated by a MIB 
		Explorer monitor alarm. 

		The objects agentppExplAlarmSourceAddress and
		agentppExplAlarmSourceDomain are not included in
		this definition but may be optionally appended if the
		corresponding information is available when this
		notification is being generated."
	::= { agentppExplTraps 2 }


agentppExplAlarmERROR NOTIFICATION-TYPE
	OBJECTS {
		agentppExplAlarmText,
		agentppExplAlarmType,
		agentppExplAlarmGenerator,
		agentppExplAlarmSourceDescr}
	STATUS current
	DESCRIPTION
		"This notification defines an alarm with ERROR severity.
		The ERROR severity designates error events that might
		still allow the system to continue running, but might 
		need immediate intervention. 

		The payload includes information generated by a MIB 
		Explorer monitor alarm. 

		The objects agentppExplAlarmSourceAddress and
		agentppExplAlarmSourceDomain are not included in
		this definition but may be optionally appended if the
		corresponding information is available when this
		notification is being generated."
	::= { agentppExplTraps 3 }


agentppExplAlarmFATAL NOTIFICATION-TYPE
	OBJECTS {
		agentppExplAlarmText,
		agentppExplAlarmType,
		agentppExplAlarmGenerator,
		agentppExplAlarmSourceDescr}
	STATUS current
	DESCRIPTION
		"This notification defines an alarm with FATAL severity.
		The FATAL severity designates very severe error events 
		that will presumably lead a system to abort.

		The payload includes information generated by a MIB 
		Explorer monitor alarm. 

		The objects agentppExplAlarmSourceAddress and
		agentppExplAlarmSourceDomain are not included in
		this definition but may be optionally appended if the
		corresponding information is available when this
		notification is being generated."
	::= { agentppExplTraps 4 }

agentppExplAlarmGroup OBJECT-GROUP
	OBJECTS {
		agentppExplAlarmText,
		agentppExplAlarmType,
		agentppExplAlarmGenerator,
		agentppExplAlarmSourceAddress,
		agentppExplAlarmSourceDomain,
		agentppExplAlarmSourceDescr }
	STATUS current
	DESCRIPTION
		"This object group includes all objects needed to
		implement a MIB Explorer alarm."
	::= { agentppExplObjectGroups 1 }

agentppExplAlarmNotifications NOTIFICATION-GROUP
	NOTIFICATIONS {
		agentppExplAlarmINFO,
		agentppExplAlarmWARN,
		agentppExplAlarmERROR,
		agentppExplAlarmFATAL }
	STATUS current
	DESCRIPTION
		"This notification group includes all notifications
		defined for alarm generation."
	::= { agentppExplNotificationGroups 1 }

END
